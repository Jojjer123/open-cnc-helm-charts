module sysrepo-module-dependencies {

  yang-version 1;

  namespace "urn:ietf:params:xml:ns:yang:sysrepo-module-dependencies";

  prefix srmd;

  organization "sysrepo.org";

  contact
    "sysrepo-devel@sysrepo.org";

  description
    "List of dependencies stored for each module by sysrepo.
     Used only internally by Sysrepo Engine.";

  revision "2017-04-21" {
    description "added installed node, other module flags decription enhanced";
  }

  revision "2016-06-14" {
    description "initial revision";
    reference "sysrepo.org";
  }

  list module_ {
    key "name revision";
    description "Module dependencies maintained by sysrepo.";

    leaf name {
        type string;
        description "Name of the module.";
    }

    leaf revision {
        type string;
        description "Revision of the module, can be empty.";
    }

    leaf prefix {
        type string;
        description "Prefix of the module.";
    }

    leaf namespace {
        type string;
        description "Namespace of the module.";
    }

    leaf filepath {
        type string;
        description "Path to the schema file.";
    }

    leaf latest-revision {
        type boolean;
        default true;
        description "Is this the latest revision of this module?";
    }

    leaf submodule {
        type boolean;
        default false;
        description "TRUE if this is only submodule, FALSE in case of a main module.";
    }

    leaf installed {
        type boolean;
        description "TRUE if the module was explicitly installed and not just imported.";
    }

    leaf implemented {
        type boolean;
        description "TRUE if this module is implemented (its data tree is accessible) and not just imported.";
    }

    leaf has-data {
       type boolean;
       default true;
       description "TRUE if this module defines any data-carrying elements and not only data types and identities.";
    }

    leaf has-persist {
       type boolean;
       default true;
       description "TRUE if this module has-data is true or the module defines a feature";
    }

    container dependencies {
      description "List of dependencies. Only direct (non-transitive) dependencies are stored in the data file.";

      list dependency {
        key "module-name module-revision type";
        description "An instance of module dependency.";

        leaf module-name {
            type string;
            description "Name of a module that the source module depends on.";
        }

        leaf module-revision {
            type string;
            description "Revision of a module that the source module depends on, can be empty.";
        }

        leaf type {
            type enumeration {
                enum include {
                    description "The source includes this module.";
                }
                enum import {
                    description "The source imports this module.";
                }
                enum extension {
                    description "The source is extended by this module (with an augment statement).";
                }
                enum data {
                    description "The source references data of this module (in a leafref, must, or when statements).";
                }
            }
            description "Type of the dependency.";
        }

        container orig-modules {
          when "../type = 'data'";
          description "List of modules that introduce this data dependency.";

          list orig-module {
            key "orig-module-name orig-module-revision";
            description "Data dependency originator.";

            leaf orig-module-name {
              type string;
              description "Name of a module that introduces this dependency.";
            }

            leaf orig-module-revision {
              type string;
              description "Revision of a module that introduces this dependency.";
            }
          }
        }
      }
    }

    container instance-identifiers {
      description "List of XPaths referring to all leaf(-list)s in the module with the instance-identifier type.";

      list instance-identifier {
        key "xpath orig-module-revision";
        description "Single instance identifier summary.";

        leaf xpath {
          type string;
          description "XPath (without keys) referring to a leaf or leaf-list with the instance-identifier type.";
        }

        leaf orig-module-name {
          type string;
          mandatory "true";
          description "Name of a module that defines this instance identifier.";
        }

        leaf orig-module-revision {
          type string;
          description "Revision of a module that defines this instance identifier.";
        }
      }
    }

    container op-data-subtrees {
      description "List of XPaths referring to all subtrees in the schema containing only operational data.";

      list op-data-subtree {
        key "xpath orig-module-revision";
        description "Reference to a subtree with only operational data.";

        leaf xpath {
          type string;
          description "XPath (without keys) referring to a root of a subtree carrying only operational data.";
        }

        leaf orig-module-name {
          type string;
          mandatory "true";
          description "Name of a module that defines this subtree.";
        }

        leaf orig-module-revision {
          type string;
          description "Revision of a module that defines this subtree.";
        }
      }
    }
  }
}
